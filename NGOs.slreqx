# NGOs

## Navigate Various Terrain (Functional)
The drone will be exposed to various elements. It would Be best to condition it to thrive in various terrains and weather conditions.

### Urban Pavemnt (Functional)
Concrete, sidewalks, potholes, etc.

### Woods (Functional)
Dirt, sticks, logs, leaves, etc.

### Sandy and Beach Areas (Functional)
Sand, Gravel, water splashes, etc.

### Beach Land (Functional)
Sand, gravel, Wet splashes, salted air, etc.

## Detect Enemy Vehicle (Functional)
The drone must be able to identify and locate enemy vehicles.

### Detect Vehicles (Functional)
The drone must distinguish the difference between a car and everything else. The can is slated to be red, which can make distinguishing easier or more difficult.

### Detect Enemy vehicle's precise location (Functional)
The drone must be able to track objects' relative and absolute (global) position

### Mimimize Comprmization (Functional)
We want to be able to observe without being observed

## Navigate Autonomously (Functional)
Autonomous navigation creates synergies between man and machine; the goal should not be for another person to control the drone remotely.

### Understand its Global Position (Functional)
The drone should be able to know where it is in the world

### Relative Localization (Functional)
The drone should be able to understand its immediate surroundings

### Autonomous Path Planning (Functional)
The drone should be able to chart its path in various environments

## Efficient Time Use (Functional)
Setup and breakdown should not make or break a mission

### Quick Pelooyment time (Functional)

### 40 Min Battery operation time (Functional)

### Quick retreat and pack up methodology (Functional)
